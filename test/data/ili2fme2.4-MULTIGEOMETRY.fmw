FME workspace ili2fme2.4-MULTIGEOMETRY.fmw

Parameters:
- DestDataset_ch.ehi.fme.Main =
- DestDataset_ch.ehi.fme.Main_2 =
- DestDataset_ch.ehi.fme.Main_3 =
- SourceDataset_ch.ehi.fme.Main =
- SourceDataset_ch.ehi.fme.Main_5 =
- SourceDataset_ch.ehi.fme.Main_7 =

Readers:
- ch.ehi.fme.Main_1: ch.ehi.fme.Main from $(SourceDataset_ch.ehi.fme.Main) in CH1903Plus_1.LV95/01
- ch.ehi.fme.Main_2: ch.ehi.fme.Main from $(SourceDataset_ch.ehi.fme.Main_5) in CH1903Plus_1.LV95/01
- ch.ehi.fme.Main_3: ch.ehi.fme.Main from $(SourceDataset_ch.ehi.fme.Main_7) in CH1903Plus_1.LV95/01

Writers:
- ch.ehi.fme.Main_4: ch.ehi.fme.Main to $(DestDataset_ch.ehi.fme.Main) in CH1903.LV03_swisstopo
- ch.ehi.fme.Main_5: ch.ehi.fme.Main to $(DestDataset_ch.ehi.fme.Main_2) in CH1903Plus_1.LV95/01
- ch.ehi.fme.Main_6: ch.ehi.fme.Main to $(DestDataset_ch.ehi.fme.Main_3) in CH1903Plus_1.LV95/01

Creator
    GEOMTYPE = Geometry Object
    NUM = 1
    CREATED -> create_topic_id_attributes
    CREATED -> create_topic_id_attributes_2
    CREATED -> create_topic_id_attributes_3

Bookmark: MULTIPOLYLINE 2.4->2.4
MultiPolyline24.TestA.ClassA1 (reader ch.ehi.fme.Main_2)
    attributes: xtf_id xtf_char(200), geomAttr2 xtf_buffer
    -> GeometryExtractor_2
GeometryExtractor_2
    ATTR = _geometry
    GENERATE_GEOMETRY_IDS = No
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> Cloner
Cloner
    COPIES = 2
    COPYATT = _copynum
    COPY -> TestFilter
TestFilter
    DEFAULT_VALUE = <UNFILTERED>
    TEST_LIST = "BOOL_OP,OR,COMPOSITE_TEST,""""""1"""""",TEST_CLAUSE,TEST @Value(_copynum) > 0",@Value(_copynum) > 1
    @Value(_copynum) > 1 -> VectorShifter
    @Value(_copynum) > 1 -> TestFilter__Value__copynum____1
    <UNFILTERED> -> MultiPolyline24.TestA.ClassA1 (writer ch.ehi.fme.Main_5)
    <UNFILTERED> -> TestFilter__Unfiltered_
VectorShifter
    Direction = 45
    Magnitude = 5
    PREC = 8
    -> AttributeValueMapper
    <Rejected> -> MultiPolyline24.TestA.ClassA1 (writer ch.ehi.fme.Main_5)
AttributeValueMapper
    DIRECTION = Forward (Source To Destination)
    LUT = @Value(xtf_id),@Evaluate(@Value(xtf_id)*2)
    SRC = xtf_id
    VAL_ATTR = _looked_up
    -> MultiPolyline24.TestA.ClassA1 (writer ch.ehi.fme.Main_5)
MultiPolyline24.TestA.ClassA1 (writer ch.ehi.fme.Main_5)
    attributes: xtf_id xtf_char(200), geomAttr2 xtf_buffer
TestFilter__Value__copynum____1: Inspector
TestFilter__Unfiltered_: Inspector
XTF_BASKETS (reader ch.ehi.fme.Main_2)
    attributes: xtf_topic xtf_char(34), xtf_id xtf_char(200), xtf_startstate xtf_char(250), xtf_endstate xtf_char(250)
create_topic_id_attributes_2: AttributeCreator
    ATTR_TABLE:
      SET_TO xtf_topic = MultiPolyline24.TestA
      SET_TO xtf_id = MultiPolyline24.TestA
    -> XTF_BASKETS (writer ch.ehi.fme.Main_5)
XTF_BASKETS (writer ch.ehi.fme.Main_5)
    attributes: xtf_topic xtf_char(34), xtf_id xtf_char(200), xtf_startstate xtf_char(250), xtf_endstate xtf_char(250)

Bookmark: MULTISURFACE / MULTIAREA 2.4->2.4
MultiSurfaceArea24.TestA.ClassA1 (reader ch.ehi.fme.Main_3)
    attributes: xtf_id xtf_char(200)
    -> CreateXTFAttributes-1
CreateXTFAttributes-1: AttributeCreator
    ATTR_TABLE:
      SET_TO xtf_class = MultiSurfaceArea24.TestA.ClassA1
      SET_TO xtf_basket = MultiSurfaceArea24.TestA
    -> TestFilter_2
    -> MultiSurfaceArea24.TestA.ClassA1 (writer ch.ehi.fme.Main_6)
TestFilter_2
    DEFAULT_VALUE = <UNFILTERED>
    TEST_LIST = "BOOL_OP,OR,COMPOSITE_TEST,""""""1"""""",TEST_CLAUSE,TEST @Value(xtf_id) > 1",@Value(_copynum) > 1
    @Value(_copynum) > 1 -> 3DRotator
    <UNFILTERED> -> MultiSurfaceArea24.TestA.ClassA1 (writer ch.ehi.fme.Main_6) [off]
3DRotator
    ANGLE = 44
    AXIS_CHOICE = Z Axis
    ROTATED -> AttributeValueMapper_2
AttributeValueMapper_2
    DIRECTION = Forward (Source To Destination)
    LUT = @Value(xtf_id),@Evaluate(@Value(xtf_id)*2)
    SRC = xtf_id
    VAL_ATTR = _looked_up
    -> MultiSurfaceArea24.TestA.ClassA1 (writer ch.ehi.fme.Main_6) [off]
MultiSurfaceArea24.TestA.ClassA1 (writer ch.ehi.fme.Main_6)
    attributes: xtf_id xtf_char(200)
MultiSurfaceArea24.TestA.ClassA2 (reader ch.ehi.fme.Main_3)
    attributes: xtf_id xtf_char(200)
XTF_BASKETS (reader ch.ehi.fme.Main_3)
    attributes: xtf_topic xtf_char(34), xtf_id xtf_char(200), xtf_startstate xtf_char(250), xtf_endstate xtf_char(250)
create_topic_id_attributes_3: AttributeCreator
    ATTR_TABLE:
      SET_TO xtf_topic = MultiSurfaceArea24.TestA
      SET_TO xtf_id = MultiSurfaceArea24.TestA
    -> XTF_BASKETS (writer ch.ehi.fme.Main_6)
XTF_BASKETS (writer ch.ehi.fme.Main_6)
    attributes: xtf_topic xtf_char(34), xtf_id xtf_char(200), xtf_startstate xtf_char(250), xtf_endstate xtf_char(250)
MultiSurfaceArea24.TestA.ClassA2 (writer ch.ehi.fme.Main_6)
    attributes: xtf_id xtf_char(200)

Bookmark: MULTICOORD 2.4->2.4
MultiCoord24.TestA.ClassA1 (reader ch.ehi.fme.Main_1)
    attributes: xtf_id xtf_char(200), geomAttr2 xtf_buffer
    -> MultiCoord24.TestA.ClassA1
    -> GeometryExtractor
    -> PartCounter
    -> MultiCoord24.TestA.ClassA1 (writer ch.ehi.fme.Main_4)
MultiCoord24.TestA.ClassA1 (writer ch.ehi.fme.Main_4)
    attributes: xtf_id xtf_char(200), geomAttr2 xtf_buffer
PartCounter
    COUNT_ATTR = _part_count
    RECURSIVE_PARAM = No
MultiCoord24.TestA.ClassA1: Inspector
GeometryExtractor
    ATTR = _geometry
    GENERATE_GEOMETRY_IDS = No
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> GeometryExtractor_Output
    <REJECTED> -> GeometryExtractor__Rejected_
GeometryExtractor_Output: Inspector
GeometryExtractor__Rejected_: Inspector
XTF_BASKETS (reader ch.ehi.fme.Main_1)
    attributes: xtf_topic xtf_char(34), xtf_id xtf_char(200), xtf_startstate xtf_char(250), xtf_endstate xtf_char(250)
3DForcer
    KEEPZVAL = No
    ZVALATTR = 467.123
    -> 2DForcer
2DForcer
create_topic_id_attributes: AttributeCreator
    ATTR_TABLE:
      SET_TO xtf_topic = MultiCoord24.TestA
      SET_TO xtf_id = MultiCoord24.TestA
    -> XTF_BASKETS (writer ch.ehi.fme.Main_4)
XTF_BASKETS (writer ch.ehi.fme.Main_4)
    attributes: xtf_topic xtf_char(34), xtf_id xtf_char(200), xtf_startstate xtf_char(250), xtf_endstate xtf_char(250)

FME custom transformer VectorShifter
Shifts features with valid geometry by a vector of a specified magnitude and angle (expressed as degrees counter-clockwise from the horizontal). The shift is performed in the XY-plane.
Input Ports 
    Input 
Input features must contain valid geometry.
    Output Ports
    Output 
Features are output with coordinates shifted by user-defined magnitude in user-defined direction. 
    <Rejected> 
Rejected features are output with fme_rejection_code attribute containing value INVALID_GEOMETRY_TYPE.
    Parameters 
    Magnitude
Unit value to shift features by.
    Direction
Angle in degrees to measure direction in. Expressed as degrees counter-clockwise from the horizontal.
    Coordinate Precision
Optional. Indicate to what decimal place shifted coordinates should be rounded to. 
Note: The CoordinateRounder transformer is used for this operation.

Parameters:
- Direction =
- Magnitude =
- PREC =

Input (input)
    -> GeometryFilter
Note: Reject Null geometry
GeometryFilter
    BREAK_AGG = No
    GEOM_PORT_NAMES = Null
    NULL -> AttributeCreator_2
    <UNFILTERED> -> AttributeCreator
Note: Fetch Parameters
AttributeCreator
    ATTR_TABLE:
      SET_TO VS_magnitude = $(Magnitude)
      SET_TO VS_angle = $(Direction)
    -> Offsetter
Note: X Offset= Magnitude * cos of angle / Y Offset= Magnitude * sin of angle
Offsetter
    MODE = Cartesian Coordinate
    XOFF = @Value(VS_magnitude)*@cos(@Value(VS_angle)*3.14159265359/180.0)
    YOFF = @Value(VS_magnitude)*@sin(@Value(VS_angle)*3.14159265359/180.0)
    ZOFF = 0
    OFFSET -> CoordinateRounder
Note: Round the coordinate values
CoordinateRounder
    XPREC = $(PREC)
    YPREC = $(PREC)
    ZPREC = 0
    ROUNDED -> Output (output)
Output (output)
AttributeCreator_2
    ATTR_TABLE = SET_TO fme_rejection_code = INVALID_GEOMETRY_TYPE
    -> <Rejected> (output)
<Rejected> (output)
